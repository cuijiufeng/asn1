V2XSecBaseTypes

--********************************************************************
--
--  LTE-V2X Security Base Data Types
--
--********************************************************************
DEFINITIONS AUTOMATIC TAGS ::= BEGIN

EXPORTS ALL;


-- ------------------------------------------------------------------
--
-- Integers
--
-- ------------------------------------------------------------------


Uint3  ::= INTEGER (0..7)                    -- (hex)                      07
Uint8  ::= INTEGER (0..255)                  -- (hex)                      ff
Uint16 ::= INTEGER (0..65535)                -- (hex)                   ff ff
Uint32 ::= INTEGER (0..4294967295)--<LONGLONG>-- -- (hex)             ff ff ff ff
Uint64 ::= INTEGER (0..18446744073709551615) -- (hex) ff ff ff ff ff ff ff ff

SequenceOfUint8  ::= SEQUENCE OF Uint8
SequenceOfUint16 ::= SEQUENCE OF Uint16


-- ------------------------------------------------------------------
--
-- OCTET STRING types
--
-- ------------------------------------------------------------------


Opaque ::= OCTET STRING

HashedId32 ::= OCTET STRING (SIZE(32))
HashedId10 ::= OCTET STRING (SIZE(10))
HashedId8  ::= OCTET STRING (SIZE(8))
HashedId4  ::= OCTET STRING (SIZE(4))
HashedId3  ::= OCTET STRING (SIZE(3))
SequenceOfHashedId3 ::= SEQUENCE OF HashedId3


-- ------------------------------------------------------------------
--
-- Time
--
-- ------------------------------------------------------------------


Time32 ::= Uint32
Time64 ::= Uint64

Duration ::= CHOICE  {
    microseconds     Uint16,
    milliseconds     Uint16,
    seconds          Uint16,
    minutes          Uint16,
    hours            Uint16,
    sixtyHours       Uint16,
    years            Uint16
}

ValidityPeriod ::= SEQUENCE  {
    start          Time32,
    duration       Duration
}

-- ------------------------------------------------------------------
--
-- Location
--
-- ------------------------------------------------------------------
ElevInt ::= Uint16 -- Range is from -4096 to 61439 in units of one-tenth of a meter

NinetyDegreeInt ::= INTEGER  {
    min 		(-900000000),
    max 		(900000000),
    unknown 	(900000001)
} (-900000000..900000001)

OneEightyDegreeInt ::= INTEGER  {
    min      	(-1799999999),
    max      	(1800000000),
    unknown  	(1800000001)
} (-1799999999..1800000001)

KnownLongitude ::= OneEightyDegreeInt (min..max)
UnknownLongitude ::= OneEightyDegreeInt (unknown)

Latitude ::= NinetyDegreeInt
Longitude ::= OneEightyDegreeInt
Elevation ::= ElevInt

KnownLatitude ::= NinetyDegreeInt (min..max) -- Minus 90deg to +90deg in microdegree intervals
UnknownLatitude ::= NinetyDegreeInt (unknown)

TwoDLocation ::= SEQUENCE  {
    latitude      Latitude,
    longitude     Longitude
}
PolygonalRegion ::= SEQUENCE SIZE(3..MAX) OF TwoDLocation

CircularRegion ::= SEQUENCE  {
    center          TwoDLocation,
    radius          Uint16
}

RectangularRegion ::= SEQUENCE  {
    northWest       TwoDLocation,
    southEast       TwoDLocation
}
SequenceOfRectangularRegion ::= SEQUENCE OF RectangularRegion

CountryOnly ::= Uint16

CountryAndRegions ::= SEQUENCE  {
    countryOnly    CountryOnly,
    regions        SequenceOfUint8
}

RegionAndSubregions ::= SEQUENCE  {
    region             Uint8,
    subregions         SequenceOfUint16
}
SequenceOfRegionAndSubregions ::= SEQUENCE OF RegionAndSubregions

CountryAndSubregions ::= SEQUENCE  {
    country             CountryOnly,
    regionAndSubregions  SequenceOfRegionAndSubregions
}

IdentifiedRegion ::= CHOICE  {
    countryOnly           CountryOnly,
    countryAndRegions     CountryAndRegions,
    countryAndSubregions   CountryAndSubregions,
    ...
}
SequenceOfIdentifiedRegion ::= SEQUENCE OF IdentifiedRegion

ThreeDLocation ::= SEQUENCE  {
    latitude        Latitude,
    longitude       Longitude,
    elevation       Elevation
}

GeographicRegion ::= CHOICE  {
    circularRegion      CircularRegion,
    rectangularRegion   SequenceOfRectangularRegion,
    polygonalRegion     PolygonalRegion,
    identifiedRegion    SequenceOfIdentifiedRegion,
    ...
}

-- ------------------------------------------------------------------
--
-- Crypto
--
-- ------------------------------------------------------------------

EccP256CurvePoint ::= CHOICE  {
    x-only           OCTET STRING (SIZE (32)),
    fill             NULL,
    compressed-y-0   OCTET STRING (SIZE (32)),
    compressed-y-1   OCTET STRING (SIZE (32)),
    uncompressed     SEQUENCE  {
        x OCTET STRING (SIZE (32)),
        y OCTET STRING (SIZE (32))
    }
}

EcdsaP256Signature ::= SEQUENCE  {
    rSig    EccP256CurvePoint,
    sSig    OCTET STRING (SIZE (32))
}

EccP384CurvePoint::= CHOICE {
    x-only          OCTET STRING (SIZE (48)),
    fill            NULL, -- consistency w 1363 / X9.62
    compressed-y-0  OCTET STRING (SIZE (48)),
    compressed-y-1  OCTET STRING (SIZE (48)),
    uncompressed    SEQUENCE {
        x OCTET STRING (SIZE (48)),
        y OCTET STRING (SIZE (48))
    }
}

EcdsaP384Signature ::= SEQUENCE  {
    rSig     EccP384CurvePoint,
    sSig     OCTET STRING (SIZE (48))
}

EcsigP256Signature ::= SEQUENCE {
    rSig    OCTET STRING (SIZE (32)),
    sSig    OCTET STRING (SIZE (32))
}

Signature ::= CHOICE  {
    ecdsaNistP256Signature          EcdsaP256Signature,
    ecdsaBrainpoolP256r1Signature   EcdsaP256Signature,
    ...,
    ecdsaBrainpoolP384r1Signature   EcdsaP384Signature,
    ecdsaNistP384Signature          EcdsaP384Signature,
    sm2Signature                    EcsigP256Signature
}

SymmAlgorithm ::= ENUMERATED  {
    aes128Ccm,
    ...,
    sm4Ccm
}

HashAlgorithm ::= ENUMERATED  {
    sha256,
    ...,
    sha384,
    sm3
}

BasePublicEncryptionKey ::= CHOICE {
    eciesNistP256             EccP256CurvePoint,
    eciesBrainpoolP256r1      EccP256CurvePoint,
    ...,
    ecencSm2                  EccP256CurvePoint
}

PublicEncryptionKey ::= SEQUENCE  {
    supportedSymmAlg      SymmAlgorithm,
    publicKey             BasePublicEncryptionKey
}

SymmetricEncryptionKey ::= CHOICE  {
    aes128Ccm     OCTET STRING(SIZE(16)),
    ...,
    sm4Ccm        OCTET STRING(SIZE(16))
}

EncryptionKey ::= CHOICE  {
    public               PublicEncryptionKey,
    symmetric            SymmetricEncryptionKey
}

PublicVerificationKey ::= CHOICE {
    ecdsaNistP256             EccP256CurvePoint,
    ecdsaBrainpoolP256r1      EccP256CurvePoint,
    ...,
    ecdsaBrainpoolP384r1      EccP384CurvePoint,
    ecdsaNistP384             EccP384CurvePoint,
    ecsigSm2                  EccP256CurvePoint
}

-- ------------------------------------------------------------------
--
-- AID / ITS-AID
--
-- ------------------------------------------------------------------
Aid ::= INTEGER (0..MAX)
SequenceOfAid ::= SEQUENCE OF Aid

BitmapSsp ::= OCTET STRING (SIZE(0..31))

SspValue ::= OCTET STRING (SIZE(0..31))

SspBitmask ::= OCTET STRING (SIZE(0..31))

ServiceSpecificPermissions ::= CHOICE  {
    opaque              OCTET STRING (SIZE(0..MAX)),
    ...,
    bitmapSsp           BitmapSsp
}

AidSsp ::= SEQUENCE  {
    aid                   Aid,
    ssp                   ServiceSpecificPermissions OPTIONAL
}
SequenceOfAidSsp ::= SEQUENCE OF AidSsp

BitmapSspRange ::= SEQUENCE  {
    sspValue            OCTET STRING (SIZE(1..32)),
    sspBitmask          OCTET STRING (SIZE(1..32))
}

SequenceOfOctetString ::= SEQUENCE (SIZE (0..MAX)) OF OCTET STRING (SIZE(0..MAX))

SspRange ::= CHOICE  {
    opaque              SequenceOfOctetString,
    all                 NULL,
    ... ,
    bitmapSspRange      BitmapSspRange
}

AidSspRange ::= SEQUENCE  {
    aid                 Aid,
    sspRange            SspRange OPTIONAL
}
SequenceOfAidSspRange ::= SEQUENCE OF AidSspRange

-- ------------------------------------------------------------------
--
-- Goes in certs
--
-- ------------------------------------------------------------------


SubjectAssurance ::= OCTET STRING (SIZE(1))

CrlSeries ::= Uint16


-- ------------------------------------------------------------------
--
-- Pseudonym Linkage
--
-- ------------------------------------------------------------------


IValue ::= Uint16

Hostname ::= UTF8String (SIZE(0..255))

LinkageValue ::= OCTET STRING (SIZE(9))

GroupLinkageValue ::= SEQUENCE  {
    jValue  OCTET STRING (SIZE(4)),
    value   OCTET STRING (SIZE(9))
}

LaId ::= OCTET STRING (SIZE(2))

LinkageSeed ::= OCTET STRING (SIZE(16))

END

V2XSecDataTypes

--******************************************************************************
--
-- LTE-V2X Security Data Types
--
--******************************************************************************

DEFINITIONS AUTOMATIC TAGS ::= BEGIN

EXPORTS ALL;

IMPORTS
  CrlSeries,
  EccP256CurvePoint,
  EncryptionKey,
  GeographicRegion,
  GroupLinkageValue,
  HashAlgorithm,
  HashedId3,
  HashedId8,
  HashedId32,
  Hostname,
  IValue,
  LinkageValue,
  Opaque,
  Aid,
  AidSsp,
  AidSspRange,
  PublicEncryptionKey,
  PublicVerificationKey,
  SequenceOfHashedId3,
  SequenceOfAidSsp,
  SequenceOfAidSspRange,
  ServiceSpecificPermissions,
  Signature,
  SubjectAssurance,
  SymmetricEncryptionKey,
  ThreeDLocation,
  Time64,
  Uint3,
  Uint8,
  Uint16,
  Uint32,
  ValidityPeriod
FROM V2XSecBaseTypes
;

--**********************************************************************
--
--  Certificates and other security management data structures
--
--**********************************************************************

CertificateType  ::= ENUMERATED {
    explicit,
    reserved,
    ...
}

IssuerIdentifier ::= CHOICE {
    sha256AndDigest         HashedId8,
    self                    HashAlgorithm,
    ...,
    sha384AndDigest         HashedId8,
    sm3AndDigest            HashedId8
}

LinkageData ::= SEQUENCE  {
    iCert                 IValue,
    linkage-value         LinkageValue,
    group-linkage-value   GroupLinkageValue OPTIONAL
}

CertificateId ::= CHOICE  {
    linkageData     LinkageData,
    name            Hostname,
    binaryId        OCTET STRING(SIZE(1..64)),
    none            NULL,
    ...
}

SubjectPermissions ::= CHOICE {
    explicit    SequenceOfAidSspRange,
    all         NULL,
    ...
}

EndEntityType ::= BIT STRING {app (0), enroll (1) } (SIZE (8)) (ALL EXCEPT {})

AidGroupPermissions ::= SEQUENCE  {
    subjectPermissions      SubjectPermissions,
    minChainLength          INTEGER DEFAULT 1,
    chainLengthRange        INTEGER DEFAULT 0,
    eeType                  EndEntityType DEFAULT {app}
}
SequenceOfAidGroupPermissions ::= SEQUENCE OF AidGroupPermissions

VerificationKeyIndicator ::= CHOICE {
    verificationKey         PublicVerificationKey,
    reconstructionValue     EccP256CurvePoint,
    ...
}

ToBeSignedCertificate ::= SEQUENCE {
    id                     CertificateId,
    cracaId                HashedId3,
    crlSeries              CrlSeries,
    validityPeriod         ValidityPeriod,
    region                 GeographicRegion OPTIONAL,
    assuranceLevel         SubjectAssurance OPTIONAL,
    appPermissions         SequenceOfAidSsp OPTIONAL,
    certIssuePermissions   SequenceOfAidGroupPermissions OPTIONAL,
    certRequestPermissions SequenceOfAidGroupPermissions OPTIONAL,
    canRequestRollover     NULL OPTIONAL,
    encryptionKey          PublicEncryptionKey OPTIONAL,
    verifyKeyIndicator     VerificationKeyIndicator,
    ...
}
(WITH COMPONENTS { ..., appPermissions PRESENT} |
 WITH COMPONENTS { ..., certIssuePermissions PRESENT} |
 WITH COMPONENTS { ..., certRequestPermissions PRESENT})

CertificateBase ::= SEQUENCE {
    version         Uint8 (3),
    type            CertificateType,
    issuer          IssuerIdentifier,
    toBeSigned      ToBeSignedCertificate,
    signature       Signature OPTIONAL
}

ExplicitCertificate ::= CertificateBase (WITH COMPONENTS {...,
    type(explicit),
    toBeSigned(WITH COMPONENTS {...,
        verifyKeyIndicator(WITH COMPONENTS {verificationKey})
    }),
    signature PRESENT
})

Reserved ::= CertificateBase (WITH COMPONENTS {...,
    type(reserved),
    toBeSigned(WITH COMPONENTS {...,
      verifyKeyIndicator(WITH COMPONENTS {reconstructionValue})
    }),
    signature ABSENT
})

-- Certificates is explicit (type = explicit,
-- toBeSigned includes verification key, signature present) or Reserved （Reserved for impilict cert）.
Certificate ::= CertificateBase (ExplicitCertificate | Reserved)
SequenceOfCertificate ::= SEQUENCE OF Certificate


--**********************************************************************
--
--  Structures for describing encrypted data
--
--**********************************************************************

PreSharedKeyRecipientInfo ::= HashedId8

One28BitCcmCiphertext ::= SEQUENCE {
    nonce           OCTET STRING (SIZE (12)),
    ccmCiphertext   Opaque --16 bytes longer than plaintext
}

SymmetricCiphertext ::= CHOICE {
    aes128ccm       One28BitCcmCiphertext,
    ...,
    sm4Ccm          One28BitCcmCiphertext
}

SymmRecipientInfo ::= SEQUENCE {
    recipientId     HashedId8,
    encKey          SymmetricCiphertext
}

EciesP256EncryptedKey ::= SEQUENCE {
    v       EccP256CurvePoint,
    c       OCTET STRING (SIZE (16)),
    t       OCTET STRING (SIZE (16))
}

EcencP256EncryptedKey ::= SEQUENCE {
    v       EccP256CurvePoint,
    t       OCTET STRING (SIZE (32)),
    c       OCTET STRING (SIZE (16))
}

EncryptedDataEncryptionKey ::= CHOICE {
    eciesNistP256           EciesP256EncryptedKey,
    eciesBrainpoolP256r1    EciesP256EncryptedKey,
    ...,
    ecencSm2                EcencP256EncryptedKey
}

PKRecipientInfo ::= SEQUENCE {
    recipientId     HashedId8,
    encKey          EncryptedDataEncryptionKey
}

RecipientInfo ::= CHOICE {
    pskRecipInfo            PreSharedKeyRecipientInfo,
    symmRecipInfo           SymmRecipientInfo,
    certRecipInfo           PKRecipientInfo,
    signedDataRecipInfo     PKRecipientInfo,
    rekRecipInfo            PKRecipientInfo
}
SequenceOfRecipientInfo ::= SEQUENCE OF RecipientInfo

EncryptedData ::= SEQUENCE {
    recipients     SequenceOfRecipientInfo,
    ciphertext     SymmetricCiphertext
}

--
--*********************************************************************
--
--  Structures for describing secured data
--
--*********************************************************************

-- this structure belongs later in the file but putting it here avoids
-- compiler errors with certain tools

SignerIdentifier ::= CHOICE  {
    digest          HashedId8,
    certificate     SequenceOfCertificate,
    self            NULL,
    ...,
    x509            OCTET STRING
}

PduFunctionalType ::= INTEGER (0..255)
  tlsHandshake           PduFunctionalType ::= 1
  iso21177ExtendedAuth   PduFunctionalType ::= 2

MissingCrlIdentifier ::= SEQUENCE  {
    cracaId         HashedId3,
    crlSeries       CrlSeries,
    ...
}

HeaderInfo ::= SEQUENCE  {
    aid                    Aid,
    generationTime         Time64 OPTIONAL,
    expiryTime             Time64  OPTIONAL,
    generationLocation     ThreeDLocation OPTIONAL,
    p2pcdLearningRequest   HashedId3 OPTIONAL,
    missingCrlIdentifier   MissingCrlIdentifier OPTIONAL,
    encryptionKey          EncryptionKey OPTIONAL,
    ...,
    inlineP2pcdRequest     SequenceOfHashedId3 OPTIONAL,
    requestedCertificate   Certificate OPTIONAL,
    pduFunctionalType      PduFunctionalType OPTIONAL
}

V2XSecData ::= SEQUENCE  {
    protocolVersion    Uint8 (3),
    content            V2XSecContent
}

HashedData::= CHOICE  {
    sha256HashedData     OCTET STRING (SIZE(32)),
    ...,
    sha384HashedData     OCTET STRING (SIZE(48)),
    sm3HashedData        OCTET STRING (SIZE(32))
}

SignedDataPayload ::= SEQUENCE  {
    data              V2XSecData OPTIONAL,
    extDataHash       HashedData OPTIONAL,
    ...
}(WITH COMPONENTS {..., data PRESENT} |
     WITH COMPONENTS {..., extDataHash PRESENT})

ToBeSignedData ::= SEQUENCE  {
    payload         SignedDataPayload,
    headerInfo      HeaderInfo
}

SignedData ::= SEQUENCE  {
    hashId          HashAlgorithm,
    tbsData         ToBeSignedData,
    signer          SignerIdentifier,
    signature       Signature
}

V2XSecContent ::=  CHOICE  {
    unsecuredData            Opaque,
    signedData               SignedData,
    encryptedData            EncryptedData,
    signedCertificateRequest Opaque,
    ...
}

Countersignature ::= V2XSecData (WITH COMPONENTS {...,
  content (WITH COMPONENTS {...,
    signedData  (WITH COMPONENTS {...,
      tbsData (WITH COMPONENTS {...,
        payload (WITH COMPONENTS {...,
          data ABSENT,
          extDataHash PRESENT
        }),
        headerInfo(WITH COMPONENTS {...,
          generationTime PRESENT,
          expiryTime ABSENT,
          generationLocation ABSENT,
          p2pcdLearningRequest ABSENT,
          missingCrlIdentifier ABSENT,
          encryptionKey ABSENT
        })
      })
    })
  })
})
END


TRCL-RootCtl
DEFINITIONS AUTOMATIC TAGS ::= BEGIN
EXPORTS ALL;
IMPORTS
  Certificate,
  IssuerIdentifier
FROM V2XSecDataTypes
  Signature,
  Time32,
  Uint8,
  Uint16
FROM V2XSecBaseTypes
;

PkiCtlInfo ::= SEQUENCE  {
    rootCertificate   Certificate,
    caListUrl         UTF8String (SIZE (0..511)) OPTIONAL
}
SequenceOfPkiCtlInfo ::= SEQUENCE OF PkiCtlInfo

ToBeSignedRootCtl ::= SEQUENCE  {
    version           Uint8 (1),
    issuer            IssuerIdentifier,
    series            Uint16,
    issueDate         Time32,
    nextRootCtl       Time32,
    pkiCtlInfoList    SequenceOfPkiCtlInfo
}

  RootCtl ::= SEQUENCE {
    toBeSignedRootCtl   ToBeSignedRootCtl,
    signature           Signature
  }
END


TDCL-PkiCtl
DEFINITIONS AUTOMATIC TAGS ::= BEGIN
EXPORTS ALL;
IMPORTS
  IssuerIdentifier,
  SequenceOfCertificate
FROM V2XSecDataTypes
  Uint8,
  Uint16,
  Signature,
  Time32
FROM V2XSecBaseTypes
;

PkiCertInfo ::= SEQUENCE  {
  certificate   SequenceOfCertificate,
  crlUrl        UTF8String (SIZE (0..511)) OPTIONAL,
  maUrl         UTF8String (SIZE (0..511)) OPTIONAL
}
SequenceOfPkiCertInfo ::= SEQUENCE OF PkiCertInfo

ToBeSignedPkiCtl ::= SEQUENCE  {
    version           Uint8,
    issuer            IssuerIdentifier,
    series            Uint16,
    issueDate         Time32,
    nextPkiCtl        Time32,
    pkiCertInfoList   SequenceOfPkiCertInfo
}

PkiCtl ::= SEQUENCE {
    toBeSignedPkiCtl  ToBeSignedPkiCtl,
    signature         Signature
}
SequenceOfPkiCtl ::= SEQUENCE OF PkiCtl
END


ScmsAcaEeInterface DEFINITIONS AUTOMATIC TAGS ::= BEGIN
EXPORTS ALL;
IMPORTS
  Time32,
  Uint8
FROM V2XSecBaseTypes
  Certificate
FROM V2XSecDataTypes
;
  AcaEeCertResponse ::= SEQUENCE {
    version           Uint8 (1),
    generationTime    Time32,
    certificate       Certificate,
    privateKeyInfo    OCTET STRING (SIZE (32)) OPTIONAL,
    ...
  }
  AcaEeInterfacePdu::= CHOICE {
    acaEeCertResponse   AcaEeCertResponse,
    ...
  }
END


ScmsAcaLaInterface
DEFINITIONS
AUTOMATIC TAGS
::=
BEGIN
EXPORTS ALL;
  AcaLaInterfacePdu ::= NULL
END


ScmsAcaMaInterface
DEFINITIONS AUTOMATIC TAGS ::= BEGIN
EXPORTS ALL;
  AcaMaInterfacePdu ::= NULL
END


ScmsEcaEeInterface
DEFINITIONS AUTOMATIC TAGS ::= BEGIN
EXPORTS ALL;
IMPORTS
  EccP256CurvePoint,
  HashedId8,
  PublicVerificationKey,
  Time32,
  Uint8
FROM V2XSecBaseTypes
  Certificate,
  CertificateType,
  SequenceOfCertificate,
  ToBeSignedCertificate
FROM V2XSecDataTypes
;

  EeEcaCertRequest ::= SEQUENCE {
    version           Uint8 (1),
    generationTime    Time32,
    type              CertificateType,
    tbsCert           ToBeSignedCertificate (WITH COMPONENTS {
      ...,
      id (WITH COMPONENTS {
        ...,
        linkageData ABSENT
      }),
      cracaId ('000000'H),
      crlSeries (0),
      appPermissions ABSENT,
      certIssuePermissions ABSENT,
      certRequestPermissions PRESENT,
      verifyKeyIndicator (WITH COMPONENTS {
        verificationKey
      })
    }),
    canonicalId       IA5String OPTIONAL,
    ...
  }

  EcaEeCertResponse ::= SEQUENCE {
    version           Uint8 (1),
    requestHash       HashedId8,
    ecaCertChain      SequenceOfCertificate,
    certificate       Certificate,
    privateKeyInfo    OCTET STRING (SIZE(32)) OPTIONAL,
    ...
  }

  EcaEeInterfacePdu::= CHOICE {
    eeEcaCertRequest   EeEcaCertRequest,
    ecaEeCertResponse  EcaEeCertResponse,
    ...
  }
END

ScmsEeMaInterface
DEFINITIONS AUTOMATIC TAGS ::= BEGIN
EXPORTS ALL;
  EeMaInterfacePdu ::= NULL
END


ScmsLaMaInterface
DEFINITIONS AUTOMATIC TAGS ::= BEGIN
EXPORTS ALL;
IMPORTS
  HashedId8,
  IValue,
  LaId,
  LinkageSeed,
  LinkageValue,
  Uint32
FROM V2XSecBaseTypes
;

  IndividualLV ::= SEQUENCE {
    iValue    IValue,
    lv        LinkageValue
  }

  GroupLV ::= SEQUENCE {
    iValue    IValue,
    j         Uint32,
    lv        LinkageValue
  }

  MaLaLinkageSeedRequest ::= SEQUENCE{
    maId     	      OCTET STRING (SIZE(0..255)),
    individualLVs   SEQUENCE (SIZE(0..MAX)) OF IndividualLV,
    groupLVs        SEQUENCE (SIZE(0..MAX)) OF GroupLV
  }

  IndividualLSInfo ::= SEQUENCE {
    i     IValue,
    lv    LinkageValue,
    ls    LinkageSeed
  }

  GroupLSInfo ::= SEQUENCE {
    i     IValue,
    j     Uint32,
    lv    LinkageValue,
    ls    LinkageSeed
  }

  LaMaLinkageSeedResponse ::= SEQUENCE{
    requestHash         HashedId8,
    laId                LaId,
    individualLSInfos   SEQUENCE (SIZE(0..MAX)) OF IndividualLSInfo,
    groupLSInfos        SEQUENCE (SIZE(0..MAX)) OF GroupLSInfo
  }

  LaMaInterfacePdu ::= CHOICE {
    maLaLinkageSeedRequest    MaLaLinkageSeedRequest,
    laMaLinkageSeedResponse   LaMaLinkageSeedResponse,
    ...
  }
END


CrlSsp
DEFINITIONS AUTOMATIC TAGS ::= BEGIN
EXPORTS ALL;
IMPORTS
  CrlSeries,
  Uint8
FROM V2XSecBaseTypes
;

CracaType ::= ENUMERATED {isCraca, issuerIsCraca}

PermissibleCrls ::= SEQUENCE OF CrlSeries

CrlSsp::= SEQUENCE  {
    version         Uint8 (1),
    associatedCraca CracaType,
    crls            PermissibleCrls,
    ...
}
END


CrlBaseTypes
DEFINITIONS AUTOMATIC TAGS ::= BEGIN
EXPORTS ALL;
IMPORTS
  CrlSeries,
  GeographicRegion,
  HashedId8,
  HashedId10,
  IValue,
  LaId,
  LinkageSeed,
  Opaque,
  Aid,
  Signature,
  Time32,
  Uint3,
  Uint8,
  Uint16,
  Uint32,
  ValidityPeriod
FROM V2XSecBaseTypes
;

--
--
--  CRL contents
--
--

CrlPriorityInfo ::= SEQUENCE {
    priority    Uint8 OPTIONAL,
    ...
}

HashBasedRevocationInfo ::= SEQUENCE {
    id          HashedId10,
    expiry      Time32,
    ...
}
SequenceOfHashBasedRevocationInfo ::= SEQUENCE OF HashBasedRevocationInfo

ToBeSignedHashIdCrl ::= SEQUENCE {
    crlSerial       Uint32,
    entries         SequenceOfHashBasedRevocationInfo,
    ...
}

IndividualRevocation ::= SEQUENCE {
    linkageSeed1    LinkageSeed,
    linkageSeed2    LinkageSeed,
    ...
}
SequenceOfIndividualRevocation ::= SEQUENCE OF IndividualRevocation

SequenceOfLinkageSeed ::= SEQUENCE OF LinkageSeed

IMaxGroup ::= SEQUENCE {
    iMax            Uint16,
    contents        SequenceOfIndividualRevocation,
    ...,
    singleSeeds     SequenceOfLinkageSeed
}
SequenceOfIMaxGroup ::= SEQUENCE OF IMaxGroup

LAGroup ::= SEQUENCE {
    la1Id       LaId,
    la2Id       LaId,
    contents    SequenceOfIMaxGroup,
    ...
}
SequenceOfLAGroup ::= SEQUENCE OF LAGroup

JMaxGroup ::= SEQUENCE {
    jmax        Uint8,
    contents    SequenceOfLAGroup,
    ...
}
SequenceOfJMaxGroup ::= SEQUENCE OF JMaxGroup

GroupCrlEntry ::= SEQUENCE {
    iMax            Uint16,
    la1Id           LaId,
    linkageSeed1    LinkageSeed,
    la2Id           LaId,
    linkageSeed2    LinkageSeed,
    ...
}
SequenceOfGroupCrlEntry ::= SEQUENCE OF GroupCrlEntry

GroupSingleSeedCrlEntry ::= SEQUENCE {
    iMax            Uint16,
    laId            LaId,
    linkageSeed     LinkageSeed
}
SequenceOfGroupSingleSeedCrlEntry ::= SEQUENCE OF GroupSingleSeedCrlEntry

ToBeSignedLinkageValueCrl ::= SEQUENCE {
    iRev                IValue,
    indexWithinI        Uint8,
    individual          SequenceOfJMaxGroup OPTIONAL,
    groups              SequenceOfGroupCrlEntry OPTIONAL,
    ...,
    groupsSingleSeed    SequenceOfGroupSingleSeedCrlEntry OPTIONAL
}
(WITH COMPONENTS {..., individual PRESENT} |
 WITH COMPONENTS {..., groups PRESENT})

CrlContents ::= SEQUENCE {
    version         Uint8 (1),
    crlSeries       CrlSeries,
    crlCraca        HashedId8,
    issueDate       Time32,
    nextCrl         Time32,
    priorityInfo    CrlPriorityInfo,
    typeSpecific    CHOICE {
        fullHashCrl         ToBeSignedHashIdCrl,
        deltaHashCrl        ToBeSignedHashIdCrl,
        fullLinkedCrl       ToBeSignedLinkageValueCrl,
        deltaLinkedCrl      ToBeSignedLinkageValueCrl,
        ...
    }
}
END


CrlDataTypes
DEFINITIONS AUTOMATIC TAGS ::= BEGIN
EXPORTS ALL;
IMPORTS
  V2XSecData
FROM V2XSecDataTypes
  Opaque,
  Aid
FROM V2XSecBaseTypes
  CrlContents
FROM CrlBaseTypes
;

CrlAid ::= Aid(3628)

SecuredCrl ::= V2XSecData (WITH COMPONENTS {...,
  content (WITH COMPONENTS {
    signedData (WITH COMPONENTS {...,
      tbsData (WITH COMPONENTS {
        payload (WITH COMPONENTS {...,
          data (WITH COMPONENTS {...,
             content (WITH COMPONENTS {
                unsecuredData (CONTAINING CrlContents)
            })
          })
        }),
        headerInfo (WITH COMPONENTS {...,
          aid (CrlAid),
          generationTime ABSENT,
          expiryTime ABSENT,
          generationLocation ABSENT,
          p2pcdLearningRequest ABSENT,
          missingCrlIdentifier ABSENT,
          encryptionKey ABSENT
        })
      })
    })
  })
})
END


ScmsMaRaInterface
DEFINITIONS AUTOMATIC TAGS ::= BEGIN
EXPORTS ALL;
  MaRaInterfacePdu ::= NULL
END

ScmsCertManagement
DEFINITIONS AUTOMATIC TAGS ::= BEGIN
EXPORTS ALL;
IMPORTS
  Time32,
  Uint8
FROM V2XSecBaseTypes
  Certificate,
  SequenceOfCertificate
FROM V2XSecDataTypes
  SecuredCrl
FROM CrlDataTypes
;
  CompositeCrl ::= SEQUENCE {
    crl   SEQUENCE SIZE (0..MAX) OF SecuredCrl,
    ...
  }

  CertificateChain ::= SEQUENCE {
    others    SEQUENCE SIZE (0..MAX) OF Certificate,
    ...
  }

  CertManagementPdu ::= CHOICE {
    compositeCrl        CompositeCrl,
    certificateChain    CertificateChain,
    ...
  }
END


ScmsLaRaInterface
DEFINITIONS AUTOMATIC TAGS ::= BEGIN
EXPORTS ALL;
IMPORTS
  Hostname,
  LaId,
  Uint8,
  Uint16,
  Uint32
FROM V2XSecBaseTypes
  EncryptedData,
  RecipientInfo
FROM V2XSecDataTypes
;

  PraLaRequestHeader ::= SEQUENCE{
    iMin     Uint16,
    iMax     Uint16,
    praId    Hostname,
    pcaId    Hostname
  }

  LinkageChainId ::= EncryptedData (WITH COMPONENTS {
    recipients (SIZE (1) INTERSECTION (WITH COMPONENT (
      RecipientInfo (WITH COMPONENTS {
        certRecipInfo
      })
    ))),
    ciphertext
  })

  PraLaIndividualLinkageValueRequest ::= SEQUENCE {
    header              PraLaRequestHeader,
    jMax                Uint8,
    numberOfFreshInd    Uint32 OPTIONAL,
    continuationsInd    SEQUENCE OF LinkageChainId OPTIONAL
  }

  PraLaGroupLinkageValueRequest ::= SEQUENCE {
    header             PraLaRequestHeader,
    jMax               Uint32,
    groupIdentifier    OCTET STRING (SIZE(4))
  }

  PraLaLinkageValueRequest ::= CHOICE {
    individualLVRequest    PraLaIndividualLinkageValueRequest,
    groupLVRequest         PraLaGroupLinkageValueRequest
  }

  EncryptedIndividualLV ::= SEQUENCE {
    version    Uint8(1),
    laId       LaId,
    enc-lv     EncryptedData (WITH COMPONENTS {
      recipients (SIZE (1) INTERSECTION (WITH COMPONENT (
        RecipientInfo (WITH COMPONENTS {
          certRecipInfo
        })
      ))),
      ciphertext
    })
  }

  IndividualLVResponseLinkageChain ::= SEQUENCE {
    jMax              Uint8,
    values            SEQUENCE OF SEQUENCE OF	EncryptedIndividualLV,
    linkageChainId    LinkageChainId
  }

  EncryptedGroupLV ::= SEQUENCE {
    version         Uint8(1),
    laId            LaId,
    enc-lv          EncryptedData (WITH COMPONENTS {
      recipients (SIZE (1) INTERSECTION (WITH COMPONENT (
        RecipientInfo (WITH COMPONENTS {
          certRecipInfo
        })
      ))),
      ciphertext
    })
  }

  GroupLVResponseLinkageChain ::= SEQUENCE {
    jMax               Uint32,
    values             SEQUENCE OF SEQUENCE OF EncryptedGroupLV,
    groupIdentifier    OCTET STRING (SIZE(4))
  }

  LaPraLinkageValueResponse ::= SEQUENCE {
    iMin             Uint16,
    iMax             Uint16,
    individualLVs    SEQUENCE (SIZE (0..MAX)) OF IndividualLVResponseLinkageChain,
    groupLVs         SEQUENCE (SIZE (0..MAX)) OF GroupLVResponseLinkageChain
  }

  LaRaInterfacePdu ::= CHOICE {
    praLaLinkageValueRequest     PraLaLinkageValueRequest,
    laPraLinkageValueResponse    LaPraLinkageValueResponse,
    ...
  }
END


ScmsEeRaInterface
DEFINITIONS AUTOMATIC TAGS ::= BEGIN
EXPORTS ALL;
IMPORTS
  HashedId8,
  IValue,
  Opaque,
  PublicEncryptionKey,
  PublicVerificationKey,
  Time32,
  Uint8
FROM V2XSecBaseTypes
  CertificateType,
  ToBeSignedCertificate
FROM V2XSecDataTypes
  EeEcaCertRequestSpdu
FROM ScmsProtocol
;
  ButterflyExpansion ::= CHOICE {
    aes128    OCTET STRING (SIZE(16)),
    ...,
    sm4       OCTET STRING (SIZE(16))
  }

  ButterflyParamsOriginal ::= SEQUENCE {
    signingExpansion      ButterflyExpansion,
    encryptionKey         PublicEncryptionKey,
    encryptionExpansion   ButterflyExpansion
  }

  AdditionalParams ::= CHOICE {
    original          ButterflyParamsOriginal,
    unified           ButterflyExpansion,
    compactUnified    ButterflyExpansion,
    encryptionKey     PublicEncryptionKey,
    ...
  }

  AaaAuthorizationInfo ::= SEQUENCE {
    aaaAuthorizationInfo    Opaque,
    aaaUrl                  UTF8String (SIZE(0..511)) OPTIONAL
  }
  SequenceOfAaaAuthorizationInfo ::= SEQUENCE OF AaaAuthorizationInfo

  EeRaCertRequest ::= SEQUENCE {
    version           Uint8 (1),
    generationTime    Time32,
    type              CertificateType,
    tbsCert           ToBeSignedCertificate (WITH COMPONENTS {
      ...,
      cracaId ('000000'H),
      crlSeries (0),
      appPermissions PRESENT,
      certIssuePermissions ABSENT,
      certRequestPermissions ABSENT,
      verifyKeyIndicator (WITH COMPONENTS {
        verificationKey
      })
    }),
    additionalParams          AdditionalParams OPTIONAL,
    ...,
    aaaAuthorizationInfoList  SequenceOfAaaAuthorizationInfo OPTIONAL
  }

  RaEeCertAck ::= SEQUENCE {
    version           Uint8 (1),
    generationTime    Time32,
    requestHash       HashedId8,
    nextDlTime        Time32,
    ...
  }

  RaEeCertInfo ::= SEQUENCE {
    version           Uint8 (1),
    generationTime    Time32,
    currentI          IValue,
    requestHash       HashedId8,
    nextDlTime        Time32,
    ...
  }

  EeRaDownloadRequest ::= SEQUENCE {
    generationTime    Time32,
    filename          UTF8String (SIZE(0..255)),
    ...
  }

  EeRaInterfacePdu ::= CHOICE {
    eeRaCertRequest                       EeRaCertRequest,
    raEeCertAck                           RaEeCertAck,
    raEeCertInfo                          RaEeCertInfo,
    eeRaDownloadRequest                   EeRaDownloadRequest,
    eeRaSuccessorEnrollmentCertRequest    EeEcaCertRequestSpdu,
    ...
  }
END


ScmsAcaRaInterface
DEFINITIONS AUTOMATIC TAGS ::= BEGIN
EXPORTS ALL;
IMPORTS
  HashedId8,
  LaId,
  PublicEncryptionKey,
  Time32,
  Uint8
FROM V2XSecBaseTypes
  ToBeSignedCertificate
FROM V2XSecDataTypes
  AcaEeCertResponsePlainSpdu,
  AcaEeCertResponsePrivateSpdu,
  AcaEeCertResponseCubkSpdu
FROM ScmsProtocol
  EncryptedIndividualLV
FROM ScmsLaRaInterface
;
  RaAcaCertRequestFlags ::= BIT STRING {butterflyExplicit (0), useCubk (1)} (SIZE (8))

  RaAcaCertRequest ::= SEQUENCE {
    version           Uint8 (1),
    generationTime    Time32,
    flags             RaAcaCertRequestFlags,
    linkageInfo       EncryptedIndividualLV OPTIONAL,
    certEncKey        PublicEncryptionKey OPTIONAL,
    tbsCert           ToBeSignedCertificate (WITH COMPONENTS {
      ...,
      cracaId ('000000'H),
      crlSeries (0),
      appPermissions PRESENT,
      certIssuePermissions ABSENT,
      certRequestPermissions ABSENT
    }),
    ...
  }

  AcaResponse ::= CHOICE {
    plain     AcaEeCertResponsePlainSpdu,
    private   AcaEeCertResponsePrivateSpdu,
    cubk      AcaEeCertResponseCubkSpdu,
    ...
  }

  AcaRaCertResponse ::= SEQUENCE {
    version           Uint8 (1),
    generationTime    Time32,
    requestHash       HashedId8,
    acaResponse       AcaResponse,
    ...
  }

  AcaRaInterfacePdu ::= CHOICE {
    raAcaCertRequest   RaAcaCertRequest,
    acaRaCertResponse  AcaRaCertResponse,
    ...
  }
END


ScmsProtocol
DEFINITIONS AUTOMATIC TAGS ::= BEGIN
EXPORTS ALL;
IMPORTS
  Aid,
  CrlSeries,
  EccP256CurvePoint,
  EccP384CurvePoint,
  EcdsaP256Signature,
  EcdsaP384Signature,
  GeographicRegion, 
  HashAlgorithm,
  HashedId3,
  PublicEncryptionKey,
  PublicVerificationKey,
  SequenceOfAid,
  SequenceOfAidSsp,
  Signature,
  SubjectAssurance,
  Uint8,
  Uint16,
  ValidityPeriod
FROM V2XSecBaseTypes
  Certificate,
  CertificateId,
  V2XSecData,
  SequenceOfCertificate,
  SequenceOfAidGroupPermissions,
  SignerIdentifier,
  VerificationKeyIndicator
FROM V2XSecDataTypes
  AcaEeInterfacePdu
FROM ScmsAcaEeInterface
  AcaLaInterfacePdu
FROM ScmsAcaLaInterface
  AcaMaInterfacePdu
FROM ScmsAcaMaInterface
  AcaRaInterfacePdu
FROM ScmsAcaRaInterface
  CertManagementPdu
FROM ScmsCertManagement
  EcaEeInterfacePdu
FROM ScmsEcaEeInterface
  EeMaInterfacePdu
FROM ScmsEeMaInterface
  EeRaInterfacePdu
FROM ScmsEeRaInterface
  LaMaInterfacePdu
FROM ScmsLaMaInterface
  LaRaInterfacePdu
FROM ScmsLaRaInterface
  MaRaInterfacePdu
FROM ScmsMaRaInterface
;
  SecurityMgmtAid ::= Aid (3627)

  ScmsPdu ::= SEQUENCE {
    version    Uint8 (1),
    content    CHOICE {
      aca-ee    AcaEeInterfacePdu,
      aca-la    AcaLaInterfacePdu,
      aca-ma    AcaMaInterfacePdu,
      aca-ra    AcaRaInterfacePdu,
      cert      CertManagementPdu,
      eca-ee    EcaEeInterfacePdu,
      ee-ma     EeMaInterfacePdu,
      ee-ra     EeRaInterfacePdu,
      la-ma     LaMaInterfacePdu,
      la-ra     LaRaInterfacePdu,
      ma-ra     MaRaInterfacePdu,
      ...
    }
  }


-------------------------------------------------------------------------------
--                            Parameterized Types                            --
-------------------------------------------------------------------------------


  ScmsPdu-Scoped {Pdu} ::= ScmsPdu (WITH COMPONENTS {
    ...,
    content (CONSTRAINED BY {
      Pdu
    })
  })

  V2XSecData-Unsecured {Tbu} ::= V2XSecData (WITH COMPONENTS {
    content (WITH COMPONENTS {
      ...,
      unsecuredData (CONTAINING Tbu)
    })
  })

  V2XSecData-Signed {Tbs, Aid} ::= V2XSecData (WITH COMPONENTS {
    ...,
    content (WITH COMPONENTS {
      ...,
      signedData (WITH COMPONENTS {
        ...,
        tbsData (WITH COMPONENTS {
          ...,
          payload (WITH COMPONENTS {
            ...,
            data (WITH COMPONENTS {
              ...,
              content (WITH COMPONENTS {
                unsecuredData (CONTAINING Tbs)
              })
            })
          }),
          headerInfo (WITH COMPONENTS {
            ...,
            aid (Aid),
            generationTime ABSENT,
            expiryTime ABSENT,
            generationLocation ABSENT,
            p2pcdLearningRequest ABSENT,
            missingCrlIdentifier ABSENT,
            encryptionKey ABSENT
          })
        }),
        signer (SignerSingleCert)
      })
    })
  })

  V2XSecData-Encrypted {Tbe} ::= V2XSecData (WITH COMPONENTS {
    ...,
    content (WITH COMPONENTS {
      encryptedData (CONSTRAINED BY {
        --encryption of-- Tbe
      })
    })
  })

  V2XSecData-EncryptedOpen ::= V2XSecData (WITH COMPONENTS {
    ...,
    content (WITH COMPONENTS {
      encryptedData
    })
  })

  V2XSecData-SignedCertRequest {Tbscr, Signer} ::= V2XSecData (WITH COMPONENTS {
    ...,
    content (WITH COMPONENTS {
      ...,
      signedCertificateRequest (CONTAINING 
      SignedCertificateRequest (WITH COMPONENTS {
        ...,
        tbsRequest (Tbscr),
        signer (Signer)
      }))
    })
  })
  V2XSecData-SignedEncrypted {Tbse, Aid} ::= V2XSecData-Encrypted {
    V2XSecData-Signed {
      Tbse,
      Aid
    }
  }

  V2XSecData-EncryptedSigned {Tbes, Aid} ::= V2XSecData-Signed {
    V2XSecData-Encrypted {
      Tbes
    }, 
    Aid
  }

  V2XSecData-SignedEncryptedCertRequest {Tbstecr, Signer} ::= V2XSecData-Encrypted {
    V2XSecData-SignedCertRequest {
      Tbstecr, 
      Signer
    }
  }


-------------------------------------------------------------------------------
--                                Signer Types                               --
-------------------------------------------------------------------------------


  SignerSingleCert ::= SignerIdentifier(WITH COMPONENTS {
    certificate (SequenceOfCertificate (SIZE (1)))
  })

  SignerSelf ::= SignerIdentifier(WITH COMPONENTS {
    self
  })


-------------------------------------------------------------------------------
--                            Certificate Requests                           --
-------------------------------------------------------------------------------

  ScopedCertificateRequest ::= ScmsPdu (
    ScmsPdu-Scoped {
      AcaRaInterfacePdu (WITH COMPONENTS {
        raAcaCertRequest
      })
    } |
    ScmsPdu-Scoped {
      EcaEeInterfacePdu (WITH COMPONENTS {
        eeEcaCertRequest
      })
    } |
    ScmsPdu-Scoped {
      EeRaInterfacePdu (WITH COMPONENTS {
        eeRaCertRequest
      })
    } |
    ScmsPdu-Scoped {
      EeRaInterfacePdu (WITH COMPONENTS {
        eeRaSuccessorEnrollmentCertRequest
      })
    }
  )

--asn1c will report an error when compiling ScopedCertificateRequest,
--then you may use the following ScopedCertificateRequest data structure,
--which only differs in asn.1 syntax expression without changing the actual C-OER encoding.
/*
  ScopedCertificateRequest ::= ScmsPdu (
    ScmsPdu (WITH COMPONENTS {
      ...,
      content (CONSTRAINED BY {
        AcaRaInterfacePdu (WITH COMPONENTS {
          raAcaCertRequest
        })
      })
    }) |
    ScmsPdu (WITH COMPONENTS {
      ...,
      content (CONSTRAINED BY {
        EcaEeInterfacePdu (WITH COMPONENTS {
          eeEcaCertRequest
        })
      })
    }) |
    ScmsPdu (WITH COMPONENTS {
      ...,
      content (CONSTRAINED BY {
        EeRaInterfacePdu (WITH COMPONENTS {
          eeRaCertRequest
        })
      })
    }) |
    ScmsPdu (WITH COMPONENTS {
      ...,
      content (CONSTRAINED BY {
        EeRaInterfacePdu (WITH COMPONENTS {
          eeRaSuccessorEnrollmentCertRequest
        })
      })
    })
  )
*/

  SignedCertificateRequest ::= SEQUENCE  {
    hashId        HashAlgorithm,
    tbsRequest    ScopedCertificateRequest,
    signer        SignerIdentifier,
    signature     Signature
  }


-------------------------------------------------------------------------------
--                            ACA - EE Interface                             --
-------------------------------------------------------------------------------


  AcaEeCertResponsePlainSpdu ::= V2XSecData-Unsecured {
    ScmsPdu-Scoped {
      AcaEeInterfacePdu (WITH COMPONENTS {
        acaEeCertResponse
      })
    }
  }

  AcaEeCertResponsePrivateSpdu ::= V2XSecData-EncryptedSigned {
    ScmsPdu-Scoped {
      AcaEeInterfacePdu (WITH COMPONENTS {
        acaEeCertResponse
      })
    }, 
    SecurityMgmtAid
  }

  AcaEeCertResponseCubkSpdu ::= V2XSecData-Encrypted {
    ScmsPdu-Scoped {
      AcaEeInterfacePdu (WITH COMPONENTS {
        acaEeCertResponse
      })
    }
  }


-------------------------------------------------------------------------------
--                            ACA - LA Interface                             --
-------------------------------------------------------------------------------

-------------------------------------------------------------------------------
--                            ACA - RA Interface                             --
-------------------------------------------------------------------------------


  RaAcaCertRequestSpdu ::= V2XSecData-SignedCertRequest {
    ScmsPdu-Scoped {
      AcaRaInterfacePdu (WITH COMPONENTS {
        raAcaCertRequest
      })
    },
    SignerSingleCert
  }

  AcaRaCertResponseSpdu ::= V2XSecData-Signed {
    ScmsPdu-Scoped {
      AcaRaInterfacePdu (WITH COMPONENTS {
        acaRaCertResponse
      })
    }, 
    SecurityMgmtAid
  }


-------------------------------------------------------------------------------
--                          Certificate Management                           --
-------------------------------------------------------------------------------


  CompositeCrlSpdu ::= V2XSecData-Unsecured {
    ScmsPdu-Scoped {
      CertManagementPdu (WITH COMPONENTS {
        compositeCrl
      })
    }
  }

  CertificateChainSpdu ::= V2XSecData-Unsecured {
    ScmsPdu-Scoped {
      CertManagementPdu (WITH COMPONENTS {
        certificateChain
      })
    }
  }


-------------------------------------------------------------------------------
--                            ECA - EE Interface                             --
-------------------------------------------------------------------------------


  EeEcaCertRequestSpdu ::= V2XSecData-SignedCertRequest {
    ScmsPdu-Scoped {
      EcaEeInterfacePdu (WITH COMPONENTS {
        eeEcaCertRequest
      })
    }, 
    SignerSelf
  }

  EcaEeCertResponseSpdu ::= V2XSecData-Signed {
    ScmsPdu-Scoped {
      EcaEeInterfacePdu (WITH COMPONENTS {
        ecaEeCertResponse
      })
    }, 
    SecurityMgmtAid
  }



-------------------------------------------------------------------------------
--                             EE - MA Interface                             --
-------------------------------------------------------------------------------

-------------------------------------------------------------------------------
--                             EE - RA Interface                             --
-------------------------------------------------------------------------------


  EeRaCertRequestSpdu ::= V2XSecData-SignedEncryptedCertRequest {
    ScmsPdu-Scoped {
      EeRaInterfacePdu (WITH COMPONENTS {
        eeRaCertRequest
      })
    }, 
    SignerSingleCert
  }

  EeRaCertRequestPlainSpdu ::= V2XSecData-Unsecured {
    ScmsPdu-Scoped {
      EeRaInterfacePdu (WITH COMPONENTS {
        eeRaCertRequest
      })
    }
  }

  RaEeCertAckSpdu ::= V2XSecData-Signed {
    ScmsPdu-Scoped {
      EeRaInterfacePdu (WITH COMPONENTS {
        raEeCertAck
      })
    },
    SecurityMgmtAid
  }

  RaEeCertInfoSpdu ::= V2XSecData-Unsecured {
    ScmsPdu-Scoped {
      EeRaInterfacePdu (WITH COMPONENTS {
        raEeCertInfo
      })
    }
  }

  EeRaDownloadRequestPlainSpdu ::= V2XSecData-Unsecured {
    ScmsPdu-Scoped {
      EeRaInterfacePdu (WITH COMPONENTS {
        eeRaDownloadRequest
      })
    }
  }

  EeRaDownloadRequestSpdu ::= V2XSecData-SignedEncrypted {
    ScmsPdu-Scoped {
      EeRaInterfacePdu (WITH COMPONENTS {
        eeRaDownloadRequest
      })
    },
    SecurityMgmtAid
  }

  EeRaSuccessorEnrollmentCertRequestSpdu ::= V2XSecData-SignedEncryptedCertRequest {
    ScmsPdu-Scoped {
      EeRaInterfacePdu (WITH COMPONENTS {
        eeRaSuccessorEnrollmentCertRequest
      })
    }, 
    SignerSingleCert
  }

  RaEeEnrollmentCertAckSpdu ::= V2XSecData-Signed {
    ScmsPdu-Scoped {
      EeRaInterfacePdu (WITH COMPONENTS {
        raEeCertInfo
      })
    }, 
    SecurityMgmtAid
  }


-------------------------------------------------------------------------------
--                             LA - MA Interface                             --
-------------------------------------------------------------------------------


  MaLaLinkageSeedRequestSpdu ::= V2XSecData-SignedEncrypted {
    ScmsPdu-Scoped {
      LaMaInterfacePdu (WITH COMPONENTS {
        maLaLinkageSeedRequest
      })
    },
    SecurityMgmtAid
  }

  LaMaLinkageSeedResponseSpdu ::= V2XSecData-SignedEncrypted {
    ScmsPdu-Scoped {
      LaMaInterfacePdu (WITH COMPONENTS {
        laMaLinkageSeedResponse
      })
    },
    SecurityMgmtAid
  }


-------------------------------------------------------------------------------
--                             LA - RA Interface                             --
-------------------------------------------------------------------------------


  PraLaIndividualLinkageValueRequestSpdu ::= V2XSecData-SignedEncrypted {
    ScmsPdu-Scoped {
      LaRaInterfacePdu (WITH COMPONENTS {
        praLaLinkageValueRequest (WITH COMPONENTS {
          individualLVRequest
        })
      })
    },
    SecurityMgmtAid
  }

  PraLaGroupLinkageValueRequestSpdu ::= V2XSecData-SignedEncrypted {
    ScmsPdu-Scoped {
      LaRaInterfacePdu (WITH COMPONENTS {
        praLaLinkageValueRequest (WITH COMPONENTS {
          groupLVRequest
	      })
      })
    },
    SecurityMgmtAid
  }

  LaPraLinkageValueResponseSpdu ::= V2XSecData-SignedEncrypted {
    ScmsPdu-Scoped {
      LaRaInterfacePdu (WITH COMPONENTS {
        laPraLinkageValueResponse
      })
    },
    SecurityMgmtAid
  }


-------------------------------------------------------------------------------
--                             MA - RA Interface                             --
-------------------------------------------------------------------------------

-------------------------------------------------------------------------------
--                       Service Specific Permissions                        --
-------------------------------------------------------------------------------

  RootCaSsp ::= SEQUENCE {
    version    Uint8 (1),
    ...
  }

  MaSsp ::= SEQUENCE {
    version         Uint8 (1),
    relevantAids    SequenceOfAid,
    ...
  }

  PgSsp ::= SEQUENCE {
    version    Uint8 (1),
    ...
  }

  IcaSsp ::= SEQUENCE {
    version    Uint8 (1),
    ...
  }

  EcaSsp ::= SEQUENCE {
    version    Uint8 (1),
    ...
  }

  AcaSsp ::= SEQUENCE {
    version    Uint8 (1),
    ...
  }

  CraSsp ::= SEQUENCE {
    version    Uint8 (1),
    ...
  }

  DcmSsp ::= SEQUENCE {
    version    Uint8 (1),
    ...
  }

  LaSsp ::= SEQUENCE {
    version    Uint8 (1),
    laId       Uint16,
    ...
  }

  RaSsp ::= SEQUENCE {
    version    Uint8 (1),
    ...
  }

  EeSsp ::= SEQUENCE {
    version    Uint8 (1),
    ...
  }

  ScmsSsp ::= CHOICE {
    root    RootCaSsp,
    ma      MaSsp,
    pg      PgSsp,
    ica     IcaSsp,
    eca     EcaSsp,
    cra     CraSsp,
    dcm     DcmSsp,
    aca     AcaSsp,
    la      LaSsp,
    ra      RaSsp,
    ee      EeSsp,
    ...
  }
END


CScmsPolicyTypes DEFINITIONS AUTOMATIC TAGS ::= BEGIN
    EXPORTS ALL;
    IMPORTS
        Duration,
        Opaque,
        Time32,
        Hostname,
        Uint8
    FROM V2XSecBaseTypes
        SecurityMgmtAid,
        V2XSecData-Signed
    FROM ScmsProtocol
    ;

    LocalPolicyFileSpdu::= V2XSecData-Signed {
      LocalPolicyFile,
      SecurityMgmtAid
    }

    LocalPolicyFile ::= SEQUENCE {
        version Uint8(1),
        generationTime Time32,
        scmsVersion Uint8(1),
        pcIPeriod Duration,
        pcOverlap Duration,
        rcaCertificateId Hostname,
        icaCertificateId Hostname,
        ecaCertificateId Hostname,
        praCertificateId Hostname,
        maCertificateId Hostname,
        pcRequest SEQUENCE {
            url UTF8String (SIZE (0..511)),
            retryInterval Duration DEFAULT minutes:10,
            maxRetries Uint8 DEFAULT 5
        },
        pcDownload SEQUENCE {
            url UTF8String (SIZE (0..511)),
            retryInterval Duration DEFAULT minutes:10,
            maxRetries Uint8 DEFAULT 5
        },
        ecRenew SEQUENCE {
            url UTF8String (SIZE (0..511)),
            retryInterval Duration DEFAULT minutes:10,
            maxRetries Uint8 DEFAULT 5
        },
        trclDownload SEQUENCE {
            url UTF8String (SIZE (0..511)),
            retryInterval Duration DEFAULT minutes:10,
            maxRetries Uint8 DEFAULT 5
        },
        tdclDownload SEQUENCE {
            url UTF8String (SIZE (0..511)),
            retryInterval Duration DEFAULT minutes:10,
            maxRetries Uint8 DEFAULT 5
        },
        tcmfCertDownload SEQUENCE {
            url UTF8String (SIZE (0..511)),
            retryInterval Duration DEFAULT minutes:10,
            maxRetries Uint8 DEFAULT 5
        },
        tcmfLinkCertDownload SEQUENCE {
            url UTF8String (SIZE (0..511)),
            retryInterval Duration DEFAULT minutes:10,
            maxRetries Uint8 DEFAULT 5
        },
        lpfDownload SEQUENCE {
            url UTF8String (SIZE (0..511)),
            retryInterval Duration DEFAULT minutes:10,
            maxRetries Uint8 DEFAULT 5
        },
        crlDownload SEQUENCE {
            url UTF8String (SIZE (0..511)),
            retryInterval Duration DEFAULT minutes:10,
            maxRetries Uint8 DEFAULT 5
        },
        ma SEQUENCE {
            url UTF8String (SIZE (0..511)),
            retryInterval Duration DEFAULT minutes:10,
            maxRetries Uint8 DEFAULT 5
        },
        er SEQUENCE {
            url UTF8String (SIZE (0..511)),
            retryInterval Duration DEFAULT minutes:10,
            maxRetries Uint8 DEFAULT 5
        },
        apiGwX509TlsCert Opaque OPTIONAL,
        ...
    }

END


CScmsErrorReport DEFINITIONS AUTOMATIC TAGS ::= BEGIN
    EXPORTS ALL;
    IMPORTS
        Time32,
        Uint16
    FROM V2XSecBaseTypes
        SecurityMgmtAid,
        V2XSecData-Signed
    FROM ScmsProtocol
    ;

    ErrorReport::= SEQUENCE {
        errorcode                Uint16,
        errormsg                 UTF8String (SIZE(0..1023)),
        esn                          UTF8String (SIZE(0..255)),
        generationTime     Time32,
        filename                 UTF8String (SIZE(0..255)),
        ...
    }

    ErrorReportSpdu ::= V2XSecData-Signed {
        ErrorReport,
        SecurityMgmtAid
    }
END
